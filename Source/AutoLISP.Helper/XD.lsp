(defun FetchXData(gStrAppNameMain EName / listEntData listToRet i iLim)
	(setq listEntData (entget EName (list gStrAppNameMain))
		  listEntData (assoc -3 listEntData)
		  listToRet (list nil)
	)
	(if(/= listEntData nil)
		(progn
			(setq listEntData (cdr listEntData) i 0 iLim (length listEntData))
			(while (< i iLim)
				(if (or (= (strcase gStrAppNameMain) (car (nth i listEntData))) (= (strcase gStrAppNameSub) (car (nth i listEntData))))
					(setq listToRet (append listToRet (list (cdr (cadr (nth i listEntData))))))
				)
				(setq i (+ i 1))
			)
		)
	)
	(setq listToRet (reverse (cdr listToRet)));Return
)
(defun C:XD(/ EName) (setq EName (car (entsel))) (FetchXData "ATANU_BANIK" EName))
